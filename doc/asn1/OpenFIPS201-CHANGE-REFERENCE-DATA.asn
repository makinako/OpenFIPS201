OpenFIPS201-CHANGE-REFERENCE-DATA-ADMIN-Schema DEFINITIONS IMPLICIT TAGS ::= 
BEGIN

ChangeReferenceDataKeyRequest ::= CHOICE {
	key		[0] OCTET STRING (SIZE(16..32)),

	rsaN	[1] OCTET STRING (SIZE(128..512)),
	rsaE	[2] OCTET STRING (SIZE(3)),
	rsaD	[3] OCTET STRING (SIZE(3)),

	eccW	[6] OCTET STRING (SIZE(32..48)),
	eccS	[7] OCTET STRING (SIZE(32..48)),
	smCVC	[8] OCTET STRING,

	rsaP	[16] OCTET STRING (SIZE(128..512)),
	rsaQ	[17] OCTET STRING (SIZE(64..256)),
	rsaDP	[18] OCTET STRING (SIZE(64..256)),
	rsaDQ	[19] OCTET STRING (SIZE(64..256)),
	rsaPQ	[20] OCTET STRING (SIZE(64..256)),
	
	clear	[31] NULL
}

END
