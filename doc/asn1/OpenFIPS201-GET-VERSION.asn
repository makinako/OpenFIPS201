OpenFIPS201-GET-VERSION-Schema DEFINITIONS IMPLICIT TAGS ::= 
BEGIN

GetVersionResponse ::= [APPLICATION 19] SEQUENCE {
	application	[0] UTF8String (SIZE(0..127)),
	major		[1] INTEGER (0..127),
	minor		[2] INTEGER (0..127),
	revision	[3] INTEGER (0..127),
	debug		[4] BOOLEAN
}

END
